Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Public Function PtInPline(pts As Variant, pline As AcadEntity) As Boolean
  Const radius = 0.0001 '减少此值可以增加精度
  
  Dim cir As AcadCircle
  Dim regions As Variant
  Dim reg1 As AcadRegion
  Dim reg2 As AcadRegion
  '生成圆
  Set cir = ThisDrawing.ModelSpace.AddCircle(pts, radius)
    
  '转换为面域
  Dim objToRegion(0 To 1) As Object
  Set objToRegion(0) = cir
  Set objToRegion(1) = pline
  regions = ThisDrawing.ModelSpace.AddRegion(objToRegion)
  Set reg1 = regions(0)
  Set reg2 = regions(1)
  
  reg1.Boolean acIntersection, reg2
  '判断是否相交
  PtInPline = False
'  If reg1.Area > 0 Then
  If reg1.Area > 0.9 * 3.14 * radius * radius Then
    PtInPline = True
  End If
  '删除临时生成物体
  cir.Delete
  reg1.Delete
    
End Function


Public Sub jzd()

    Dim entity As AcadEntity
    Dim text As AcadText
    Dim name As String
    Dim num As String
    Dim path As String
    Dim basePnt As Variant
    Dim polyline As AcadLWPolyline
    Dim pline As AcadEntity

    Dim s As AcadSelectionSet
    Dim ss As AcadSelectionSet
    
    If ThisDrawing.SelectionSets.Count <> 0 Then
       For Each s In ThisDrawing.SelectionSets
           s.Delete
       Next
    End If
    
    Dim gpCode(0) As Integer
    Dim dataValue(0) As Variant
    gpCode(0) = 8
    dataValue(0) = "JZD"
    
    Dim groupCode As Variant, dataCode As Variant
    groupCode = gpCode
    dataCode = dataValue
    
    Set s = ThisDrawing.SelectionSets.Add("ss")
    Set ss = ThisDrawing.SelectionSets.Add("s")
    
    s.SelectOnScreen groupCode, dataCode
    
    For Each entity In s
        If entity.ObjectName = "AcDbPolyline" Then
        
    
            Dim layer As AcadLayer
            Set layer = ThisDrawing.Layers.Add("zhuji")
            
            Set polyline = entity
            Set pline = entity
            max_x = 0
            max_y = 0
            min_x = 99999999
            min_y = 99999999
            For Index = 0 To UBound(polyline.Coordinates) / 2
                x = polyline.Coordinates(Index * 2)
                y = polyline.Coordinates(Index * 2 + 1)
                If max_x < x Then
                    max_x = x
                End If
                If max_y < y Then
                    max_y = y
                End If
                If min_x > x Then
                    min_x = x
                End If
                If min_y > y Then
                    min_y = y
                End If
            Next
            
            Dim point1a(0 To 2) As Double
            Dim point2a(0 To 2) As Double
            
            c_x = (min_x + max_x) / 2
            c_y = (min_y + max_y) / 2
            l = (max_x - min_x) / 2
            h = (max_y - min_y) / 2
            
            point1a(0) = c_x - l
            point1a(1) = c_y - h
            point2a(0) = c_x + l
            point2a(1) = c_y + h
            
            ss.Select acSelectionSetWindow, point1a, point2a, groupCode, dataCode
            
            Dim currInsertionPoint As Variant
            Dim en As AcadEntity
            
            For Each en In ss
               If en.ObjectName = "AcDbText" Then
                   Set text = en
                   name = text.TextString
                   '中文字符且长度大于1
                   currInsertionPoint = text.InsertionPoint
                   If Len(name) > 2 And InStr(name, "JC") And PtInPline(currInsertionPoint, pline) Then
                       num = name
                       Exit For
                   End If
               End If
            Next
            
            Dim t_Point(0 To 2) As Double
            
            For Index = 0 To UBound(polyline.Coordinates) / 2
                t_Point(0) = polyline.Coordinates(Index * 2)
                t_Point(1) = polyline.Coordinates(Index * 2 + 1)
                t_Point(2) = 0
                Set text = ThisDrawing.ModelSpace.AddText(num & "-" & Index + 1, t_Point, 0.5)
                text.layer = "zhuji"
                text.Update
            Next
            
        End If
        
    Next
    
    s.Delete
    ss.Delete
    
End Sub
