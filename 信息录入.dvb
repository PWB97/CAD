Attribute VB_Name = "InputForm"
Attribute VB_Base = "0{358CB7ED-5093-494F-9ADA-A6D29BACBF72}{5B3C0195-5DAA-4531-BB82-208262B7B93D}"
Attribute VB_GlobalNameSpace = False
Attribute VB_Creatable = False
Attribute VB_PredeclaredId = True
Attribute VB_Exposed = False
Attribute VB_TemplateDerived = False
Attribute VB_Customizable = False
Public xb As Integer

Private Sub Label1_Click()

End Sub

Private Sub CommandButton1_Click()
    Dim path As String
    path = ThisDrawing.s_path & InputForm.TextBox1.text & "(" & InputForm.TextBox2.text & ")\"
    If InputForm.TextBox1.text = "" Or InputForm.TextBox2.text = "" Then
        MsgBox "请输入姓名和宗地编号"
        End
    Else
        '新建保存路径
        If Dir(path, vbDirectory) = "" Then
            MkDir (path)
        End If
    End If

    Dim text As AcadText
    Dim t_Point(0 To 2) As Double
    
    t_Point(0) = ThisDrawing.cx: t_Point(1) = ThisDrawing.cy: t_Point(2) = 0
    
    If InputForm.TextBox1.text = "" Then
        Set text = ThisDrawing.ModelSpace.AddText(" ", t_Point, 2)
    Else
        Set text = ThisDrawing.ModelSpace.AddText(InputForm.TextBox1.text, t_Point, 2)
    End If
    ThisDrawing.Layers.Add ("zhuji")
    
    text.Layer = "zhuji"
    
    Dim DataType(0 To 16) As Integer
    Dim Data(0 To 16) As Variant
    
    DataType(0) = 1001: Data(0) = "Test_Application"
    DataType(1) = 1000: Data(1) = InputForm.TextBox2.text 'zdbh
    DataType(2) = 1000: Data(2) = InputForm.TextBox3.text 'dl
    DataType(3) = 1000: Data(3) = InputForm.TextBox4.text 'sfz
    DataType(4) = 1000: Data(4) = InputForm.TextBox5.text 'hkb
    DataType(5) = 1000: Data(5) = xb 'xb
    DataType(6) = 1000: Data(6) = InputForm.TextBox6.text 'year
    DataType(7) = 1000: Data(7) = InputForm.TextBox7.text 'month
    DataType(8) = 1000: Data(8) = InputForm.TextBox8.text 'day
    DataType(9) = 1000: Data(9) = InputForm.TextBox9.text 'time
    DataType(10) = 1000: Data(10) = ThisDrawing.sx 'am or pm
    DataType(11) = 1000: Data(11) = InputForm.TextBox10.text 'pro
    DataType(12) = 1000: Data(12) = InputForm.TextBox11.text 'city
    DataType(13) = 1000: Data(13) = InputForm.TextBox12.text 'x-city
    DataType(14) = 1000: Data(14) = InputForm.TextBox13.text 'co
    DataType(15) = 1000: Data(15) = InputForm.TextBox14.text 'ne
    DataType(16) = 1000: Data(16) = InputForm.TextBox15.text 'she

    text.SetXData DataType, Data
    
    InputForm.Hide
End Sub

Private Sub CommandButton2_Click()
    ThisDrawing.st = 0
    UserForm1.Show
End Sub

Private Sub CommandButton3_Click()
    ThisDrawing.st = 2
       UserForm1.Show
End Sub

Private Sub CommandButton4_Click()
    ThisDrawing.st = 1
    UserForm1.Show
End Sub

Private Sub CommandButton5_Click()
    UserForm2.Show
End Sub

Private Sub Label12_Click()

End Sub

Private Sub Label16_Click()

End Sub

Private Sub Label3_Click()

End Sub

Private Sub Label7_Click()

End Sub

Private Sub OptionButton1_Click()
    ThisDrawing.sx = 0
End Sub

Private Sub OptionButton2_Click()
    ThisDrawing.sx = 1
End Sub

Private Sub OptionButton3_Click()
    xb = 0
End Sub

Private Sub OptionButton4_Click()
    xb = 1
End Sub

Private Sub TextBox1_Change()

End Sub

Private Sub TextBox10_Change()

End Sub

Private Sub TextBox11_Change()

End Sub

Private Sub TextBox12_Change()

End Sub

Private Sub TextBox13_Change()

End Sub

Private Sub TextBox14_Change()

End Sub

Private Sub TextBox15_Change()

End Sub

Private Sub TextBox4_Change()

End Sub

Private Sub TextBox6_Change()

End Sub

Private Sub TextBox7_Change()

End Sub

Private Sub TextBox9_Change()

End Sub

Private Sub UserForm_Click()

End Sub

Private Sub UserForm_Terminate()

End Sub

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Public st As Integer
Public cx As Double
Public cy As Double
Public sx As Integer
Public pline As AcadLWPolyline
Public c_num As Integer
Public s_path As String
Public num As String

Public Function PtInPline(pts As Variant, pline As AcadEntity) As Boolean
  Const radius = 0.0001 '减少此值可以增加精度
  
  Dim cir As AcadCircle
  Dim regions As Variant
  Dim reg1 As AcadRegion
  Dim reg2 As AcadRegion
  '生成圆
  Set cir = ThisDrawing.ModelSpace.AddCircle(pts, radius)
    
  '转换为面域
  Dim objToRegion(0 To 1) As Object
  Set objToRegion(0) = cir
  Set objToRegion(1) = pline
  regions = ThisDrawing.ModelSpace.AddRegion(objToRegion)
  Set reg1 = regions(0)
  Set reg2 = regions(1)
  
  reg1.Boolean acIntersection, reg2
  '判断是否相交
  PtInPline = False
'  If reg1.Area > 0 Then
  If reg1.Area > 0.9 * 3.14 * radius * radius Then
    PtInPline = True
  End If
  '删除临时生成物体
  cir.Delete
  reg1.Delete
    
End Function

Public Sub xxlr()
    
    InputForm.Hide

    Dim group As AcadGroup
    Dim flag As Boolean
    Dim entity As AcadEntity
    Dim text As AcadText
    Dim name As String
    Dim path As String
    Dim basePnt As Variant
    Dim polyline As AcadLWPolyline
    
    path = "C:\chengguo\"
    
    If Dir(path, vbDirectory) = "" Then
        MkDir (path)
    End If

    s_path = path
    
    ThisDrawing.Utility.GetEntity entity, basePnt, "选取JZD多段线"
    
    While Not (entity.ObjectName = "AcDbPolyline" And entity.Layer = "JZD")
        MsgBox "不是多段线或不在JZD图层，重新选择"
        ThisDrawing.Utility.GetEntity entity, basePnt, "选取JZD多段线"
    Wend
    
    max_x = 0
    max_y = 0
    min_x = 99999999999#
    min_y = 99999999999#
    
    Set polyline = entity
    Set pline = entity
    c_num = UBound(polyline.Coordinates) / 2
    For Index = 0 To UBound(polyline.Coordinates) / 2
        x = polyline.Coordinates(Index * 2)
        y = polyline.Coordinates(Index * 2 + 1)
        If max_x < x Then
            max_x = x
        End If
        If max_y < y Then
            max_y = y
        End If
        If min_x > x Then
            min_x = x
        End If
        If min_y > y Then
            min_y = y
        End If
    Next
    
    c_x = (min_x + max_x) / 2
    c_y = (min_y + max_y) / 2
    l = (max_x - min_x) / 2
    h = (max_y - min_y) / 2
     
    Dim ss As AcadSelectionSet

    '选择集
    If ThisDrawing.SelectionSets.Count <> 0 Then
        For Each ss In ThisDrawing.SelectionSets
            ss.Delete
            Exit For
        Next
    End If
    
    Dim point1a(0 To 2) As Double
    Dim point2a(0 To 2) As Double
    
    point1a(0) = c_x - l
    point1a(1) = c_y - h
    point2a(0) = c_x + l
    point2a(1) = c_y + h
    
    Dim gpCode(0) As Integer
    Dim dataValue(0) As Variant
    gpCode(0) = 8
    dataValue(0) = "JZD"
    
    Dim groupCode As Variant, dataCode As Variant
    groupCode = gpCode
    dataCode = dataValue

    
    Set ss = ThisDrawing.SelectionSets.Add("s")
    ss.Select acSelectionSetWindow, point1a, point2a, groupCode, dataCode
    
    Dim cp As Variant
    
    For Each entity In ss
        If entity.ObjectName = "AcDbText" Then
            Set text = entity
            name = text.TextString
            cp = text.InsertionPoint
             If Len(name) > 2 And InStr(name, "J") And PtInPline(cp, polyline) Then
                num = name
            End If
        End If
    Next
    
    InputForm.Show

End Sub

Attribute VB_Name = "UserForm1"
Attribute VB_Base = "0{A40DDD6D-2C4A-48F2-9B83-76C003FCDF90}{BD0985CE-587F-4AE8-9F51-D8CAF7B0AD2B}"
Attribute VB_GlobalNameSpace = False
Attribute VB_Creatable = False
Attribute VB_PredeclaredId = True
Attribute VB_Exposed = False
Attribute VB_TemplateDerived = False
Attribute VB_Customizable = False
Public time As Integer

Private Declare Function GetClipboardData Lib "user32" (ByVal wFormat As Long) As Long
Private Declare Function CloseClipboard Lib "user32" () As Long
Private Declare Function OpenClipboard Lib "user32" (ByVal hwnd As Long) As Long
Private Declare Function OleCreatePictureIndirect Lib "olepro32.dll" (PicDesc As PicBmp, RefIID As Guid, ByVal fPictureOwnsHandle As Long, IPic As IPicture) As Long
Private Const CF_BITMAP = 2
Private Type PicBmp
    Size As Long
    Type As Long
    hBmp As Long
    hPal As Long
    Reserved As Long
End Type

Private Type Guid
    Data1 As Long
    Data2 As Integer
    Data3 As Integer
    Data4(0 To 7) As Byte
End Type

Private Declare Function capCreateCaptureWindow Lib "avicap32.dll" _
Alias "capCreateCaptureWindowA" ( _
ByVal lpszWindowName As String, _
ByVal dwStyle As Long, _
ByVal x As Long, _
ByVal y As Long, _
ByVal nWidth As Long, _
ByVal nHeight As Long, _
ByVal hWndParent As Long, _
ByVal nID As Long) As Long

Private Preview_Handle As Long

Private Const WS_CHILD = &H40000000
Private Const WS_VISIBLE = &H10000000
Private Const WM_USER = &H400
Private Const WM_CAP_START = &H400
Private Const WM_CAP_EDIT_COPY = (WM_CAP_START + 30)
Private Const WM_CAP_DRIVER_CONNECT = (WM_CAP_START + 10)
Private Const WM_CAP_SET_PREVIEWRATE = (WM_CAP_START + 52)
Private Const WM_CAP_SET_OVERLAY = (WM_CAP_START + 51)
Private Const WM_CAP_SET_PREVIEW = (WM_CAP_START + 50)
Private Const WM_CAP_DRIVER_DISCONNECT = (WM_CAP_START + 11)

Private Declare Function SendMessage Lib "user32" _
Alias "SendMessageA" ( _
ByVal hwnd As Long, _
ByVal wMsg As Long, _
ByVal wParam As Long, _
lParam As Any) As Long
Private Declare Function GetForegroundWindow Lib "user32.dll" () As Long

Private Function CapturePicture(nCaptureHandle As Long, path As String)
    Set Clip = CreateObject("new:{1C3B4210-F441-11CE-B9EA-00AA006B1A69}")
    SendMessage nCaptureHandle, WM_CAP_EDIT_COPY, 0, 0
    Dim Pic As PicBmp, IPic As IPicture, IID_IDispatch As Guid

    OpenClipboard 0 'OpenClipboard

    With IID_IDispatch

        .Data1 = &H20400

        .Data4(0) = &HC0

        .Data4(7) = &H46

    End With



    With Pic

        .Size = Len(Pic)

        .Type = 1

        .hBmp = GetClipboardData(CF_BITMAP)

    End With

    

    OleCreatePictureIndirect Pic, IID_IDispatch, 1, IPic
    
    stdole.SavePicture IPic, path
    
    MsgBox "已保存至" & path
    
    CloseClipboard
End Function

Private Sub CommandButton2_Click()
    time = time + 1
    UserForm1.ToggleButton1.Enabled = True
    Dim path As String
    path = ThisDrawing.s_path & InputForm.TextBox1.text & "(" & InputForm.TextBox2.text & ")\"
    If InputForm.TextBox1.text = "" Or InputForm.TextBox2.text = "" Then
        MsgBox "请输入姓名和宗地编号"
        End
    Else
        '新建保存路径
        If Dir(path, vbDirectory) = "" Then
            MkDir (path)
        End If
        If ThisDrawing.st = 0 Then
            If Dir(path & "身份证\", vbDirectory) = "" Then
                MkDir (path & "身份证\")
            End If
            path = path & "身份证\身份证" & time & ".png"
        ElseIf ThisDrawing.st = 1 Then
            If Dir(path & "户口本\", vbDirectory) = "" Then
                MkDir (path & "户口本\")
            End If
            path = path & "户口本\户口本" & time & ".png"
        Else
            If Dir(path & "立面照\", vbDirectory) = "" Then
                MkDir (path & "立面照\")
            End If
            path = path & "立面照\立面" & time & ".png"
        End If
        CapturePicture Preview_Handle, path
    End If
End Sub

Private Sub Label1_Click()

End Sub

Private Sub ToggleButton1_Click()
    If time > 0 Then
        Dim path As String
        path = ThisDrawing.s_path & InputForm.TextBox1.text & "(" & InputForm.TextBox2.text & ")\"
        If ThisDrawing.st = 0 Then
            Kill path & "身份证\身份证" & time & ".png"
        ElseIf ThisDrawing.st = 1 Then
            Kill path & "户口本\户口本" & time & ".png"
        Else
            Kill path & "立面照\立面" & time & ".png"
        End If
        time = time - 1
    Else
        UserForm1.ToggleButton1.Enabled = False
    End If
End Sub

Private Sub UserForm_Initialize()
    time = 0
    Preview_Handle = capCreateCaptureWindow("Video", WS_CHILD + WS_VISIBLE, 2, 2, 2200, 1560, ThisDrawing.hwnd, 1)
    SendMessage Preview_Handle, WM_CAP_DRIVER_CONNECT, 0, 0
    SendMessage Preview_Handle, WM_CAP_SET_PREVIEWRATE, 1, 0
    SendMessage Preview_Handle, WM_CAP_SET_PREVIEW, 1, 0
End Sub

Private Sub UserForm_Terminate()
    SendMessage Preview_Handle, WM_CAP_DRIVER_DISCONNECT, 0, 0
End Sub

Attribute VB_Name = "UserForm2"
Attribute VB_Base = "0{8265BC14-71C1-4B6E-BB53-39EAF4BD17A7}{55A03064-6C59-4777-8589-D884954D06F3}"
Attribute VB_GlobalNameSpace = False
Attribute VB_Creatable = False
Attribute VB_PredeclaredId = True
Attribute VB_Exposed = False
Attribute VB_TemplateDerived = False
Attribute VB_Customizable = False
Public i As Integer
Public a As Integer
Public b As Integer
Public c As Integer
Public text As AcadText

Private Sub CommandButton1_Click()
     i = i - 1
    If i < 0 Then
        UserForm2.CommandButton1.Enabled = False
    Else
        UserForm2.CommandButton2.Enabled = True
        jzdin i
    End If
End Sub

Private Sub CommandButton2_Click()
    i = i + 1
    If i >= ThisDrawing.c_num Then
        UserForm2.CommandButton2.Enabled = False
    Else
        UserForm2.CommandButton1.Enabled = True
        jzdin i
    End If
End Sub

Private Sub CommandButton3_Click()
     If i > -1 Then
        Dim DataType(0 To 3) As Integer
        Dim Data(0 To 3) As Variant
        
        DataType(0) = 1001: Data(0) = "Test_Application"
        DataType(1) = 1000: Data(1) = a
        DataType(2) = 1000: Data(2) = b
        DataType(3) = 1000: Data(3) = c
        
        text.SetXData DataType, Data
    Else
        MsgBox "请先点击下一个"
    End If
End Sub

Private Sub Frame3_Click()
    c = 2
End Sub

Private Sub OptionButton1_Click()
    a = 0
End Sub

Private Sub OptionButton10_Click()
    b = 5
End Sub

Private Sub OptionButton11_Click()
    c = 0
End Sub

Private Sub OptionButton12_Click()
    c = 1
End Sub

Private Sub OptionButton2_Click()
    a = 1
End Sub

Private Sub OptionButton3_Click()
     a = 2
End Sub

Private Sub OptionButton4_Click()
    a = 3
End Sub

Private Sub OptionButton5_Click()
    b = 0
End Sub

Private Sub OptionButton6_Click()
    b = 1
End Sub

Private Sub OptionButton7_Click()
    b = 2
End Sub

Private Sub OptionButton8_Click()
    b = 3
End Sub

Private Sub OptionButton9_Click()
    b = 4
End Sub

Public Sub jzdin(i As Integer)
    x = ThisDrawing.pline.Coordinates(i * 2)
    y = ThisDrawing.pline.Coordinates(i * 2 + 1)
    
    Dim ss As AcadSelectionSet
    If ThisDrawing.SelectionSets.Count <> 0 Then
       For Each ss In ThisDrawing.SelectionSets
           ss.Delete
           Exit For
       Next
    End If
    
    Dim gpCode(0) As Integer
    Dim dataValue(0) As Variant
    gpCode(0) = 8
    dataValue(0) = "zhuji"
    
    Dim groupCode As Variant, dataCode As Variant
    groupCode = gpCode
    dataCode = dataValue
    Set ss = ThisDrawing.SelectionSets.Add("s")
    
    Dim point1a(0 To 2) As Double
    Dim point2a(0 To 2) As Double
    
    point1a(0) = x - 5
    point1a(1) = y - 5
    point2a(0) = x + 5
    point2a(1) = y + 5
    
    'Dim point(0 To 2) As Double
    'point(0) = x: point(1) = y: point(2) = 0
    
    'ss.SelectAtPoint point, groupCode, dataCode
    ss.Select acSelectionSetWindow, point1a, point2a, groupCode, dataCode
    
    Dim txt As String
    Dim t As AcadText
    
    If ss.Count = 0 Then
        MsgBox ("没有找到该点，请检查图纸！第" & i + 1 & "号点")
    End If
    
    
    For Each entity In ss
        Set t = entity
        txt = t.TextString
        If txt = ThisDrawing.num & "-" & i + 1 Then
            Set text = t
            UserForm2.Label1 = txt
        End If
    Next
    
    ss.Delete
End Sub

Private Sub UserForm_Activate()
    i = -1
End Sub

Private Sub UserForm_Click()

End Sub
