Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Public Function PtInPline(pts As Variant, pline As AcadEntity) As Boolean
  Const radius = 0.0001 '减少此值可以增加精度
  
  Dim cir As AcadCircle
  Dim regions As Variant
  Dim reg1 As AcadRegion
  Dim reg2 As AcadRegion
  '生成圆
  Set cir = ThisDrawing.ModelSpace.AddCircle(pts, radius)
    
  '转换为面域
  Dim objToRegion(0 To 1) As Object
  Set objToRegion(0) = cir
  Set objToRegion(1) = pline
  regions = ThisDrawing.ModelSpace.AddRegion(objToRegion)
  Set reg1 = regions(0)
  Set reg2 = regions(1)
  
  reg1.Boolean acIntersection, reg2
  '判断是否相交
  PtInPline = False
'  If reg1.Area > 0 Then
  If reg1.Area > 0.9 * 3.14 * radius * radius Then
    PtInPline = True
  End If
  '删除临时生成物体
  cir.Delete
  reg1.Delete
    
End Function

Public Function axEnt2lspEnt(entObj As AcadEntity) As String
    Dim entHandle As String
    entHandle = entObj.Handle
    axEnt2lspEnt = "(handent" & Chr(34) & entHandle & Chr(34) & ")"
End Function

Private Function offent(obj As AcadEntity, off As Double, pt() As Double, de As Boolean) As AcadEntity
Const pi = 3.1415926
'obj为要偏移的元素，off为偏移量，正外负内，pt()为偏移后元素的一维坐标数组,de 是否删除偏移后的多段线
'如果obj为三维多段线，删除这条线，重新画一条二维多段线
Dim obj1 As AcadPolyline
Dim pl As AcadPolyline
Dim cr As AcadCircle
Select Case UCase(obj.ObjectName)
Case "ACDB3DPOLYLINE", "ACDB2DPOLYLINE"

ReDim pt(UBound(obj.Coordinates)) As Double
For i = 0 To UBound(pt) Step 3
pt(i) = obj.Coordinate(i / 3)(0)
pt(i + 1) = obj.Coordinate(i / 3)(1)
Next i
teml = obj.Layer
temc = obj.Closed

Case "ACDBPOLYLINE"
ReDim pt(((UBound(obj.Coordinates) + 1) / 2) * 3 - 1) As Double
For i = 0 To UBound(pt) Step 3
pt(i) = obj.Coordinate((i) / 3)(0)
pt(i + 1) = obj.Coordinate((i) / 3)(1)
Next i
teml = obj.Layer
temc = obj.Closed
Case "ACDBCIRCLE"
Set cr = obj
Dim pp As Double
pp = cr.radius
ReDim pt(359 * 3 + 2) As Double
For i = 0 To 359
pt(i * 3) = cr.Center(0) + Cos(i * pi / 180) * cr.radius
pt(i * 3 + 1) = cr.Center(1) + Sin(i * pi / 180) * cr.radius
pt(i * 3 + 2) = 0
Next i
teml = obj.Layer
temc = True
End Select
Set obj1 = ThisDrawing.ModelSpace.AddPolyline(pt)
obj1.Layer = teml
obj1.Closed = temc

'---------------------------------
Dim offobj As AcadEntity
Select Case off
Case Is > 0
off1 = obj1.Offset(off)
If off1(0).Area < obj1.Area Then
off1(0).Delete
off1 = obj1.Offset(-1 * off)
End If
Set offobj = off1(0)
Case Is < 0
off1 = obj1.Offset(off)
If off1(0).Area > obj1.Area Then
off1(0).Delete
off1 = obj1.Offset(-1 * off)
End If
Set offobj = off1(0)
End Select
'--------------------------------
Set offent = offobj
ReDim pt(UBound(offobj.Coordinates)) As Double
For i = 0 To UBound(pt) Step 3
pt(i) = offobj.Coordinate(i / 3)(0)
pt(i + 1) = offobj.Coordinate(i / 3)(1)
Next i
obj1.Delete
Set obj1 = Nothing
If de Then
offobj.Delete
End If
End Function

Public Sub fht()

Dim group As AcadGroup
Dim flag As Boolean
Dim entity As AcadEntity
Dim text As AcadText
Dim max_x As Double
Dim min_x As Double
Dim max_y As Double
Dim min_y As Double
Dim cor As Variant
Dim ss As AcadSelectionSet
Dim l As Double
Dim h As Double
Dim c_x As Double
Dim c_y As Double
Dim name As String
Dim num As String
Dim path As String
Dim leng As Integer
Dim pline As AcadEntity
Dim ply As AcadLWPolyline

path = "C:\chengguo\" '保存路径

If Dir(path, vbDirectory) = "" Then
    MkDir (path)
End If

For Each group In ThisDrawing.Groups
    
    flag = False
    '查找带有判断中文名字group
    For Each entity In group
        If entity.ObjectName = "AcDbText" Then
            Set text = entity
            name = text.TextString
            '中文字符且长度大于1
            If Len(name) > 2 And InStr(name, "JC") Then
                num = name
            End If
            If Len(name) > 1 And ((AscW(Mid(name, 1, 1)) > -40870 And AscW(Mid(name, 1, 1)) < -19967) Or (AscW(Mid(name, 1, 1)) < 40870 And AscW(Mid(name, 1, 1)) > 19967)) Then
                flag = True
                Exit For
            End If
        End If
    Next
    
    '找到并处理
    If flag = True Then
    
        max_x = 0
        max_y = 0
        min_x = 99999999
        min_y = 99999999
        
        '选择区域
        For Each entity In group
            If entity.ObjectName = "AcDbPolyline" Then
                Set pline = entity
                Set ply = entity
                For Index = 0 To UBound(ply.Coordinates) / 2
                    x = ply.Coordinates(Index * 2)
                    y = ply.Coordinates(Index * 2 + 1)
                    If max_x < x Then
                        max_x = x
                    End If
                    If max_y < y Then
                        max_y = y
                    End If
                    If min_x > x Then
                        min_x = x
                    End If
                    If min_y > y Then
                        min_y = y
                    End If
                Next
            End If
        Next
        
        '选择集
        If ThisDrawing.SelectionSets.Count <> 0 Then
            For Each ss In ThisDrawing.SelectionSets
                ss.Delete
                Exit For
            Next
        End If
        Set ss = ThisDrawing.SelectionSets.Add("ss")
        '新建保存路径
        If Dir(path & name & "(" & num & ")", vbDirectory) = "" Then
            MkDir (path & name & "(" & num & ")")
        End If
    
        c_x = (min_x + max_x) / 2
        c_y = (min_y + max_y) / 2
        l = (max_x - min_x) / 2
        h = (max_y - min_y) / 2
         
        Dim point1a(0 To 2) As Double
        Dim point2a(0 To 2) As Double
        Dim gpCode(0) As Integer
        Dim dataValue(0) As Variant
        Dim removeObjects(0) As AcadEntity
        
        gpCode(0) = 8
        dataValue(0) = "JMD"
        Dim groupCode As Variant, dataCode As Variant
        groupCode = gpCode
        dataCode = dataValue
        
        point1a(0) = c_x - l
        point1a(1) = c_y - h
        point2a(0) = c_x + l
        point2a(1) = c_y + h
        
        ss.Select acSelectionSetCrossing, point1a, point2a, groupCode, dataCode
        
        Dim h_type As String
        Dim f_num As String
        Dim floor As Integer
        
        Dim currInsertionPoint As Variant
        
        floor = 1
        
        Dim ACADapp As AcadApplication
            
        Set ACADapp = GetObject(, "AutoCAD.Application")
        
        Dim curdoc As AcadDocument
        
        Set curdoc = ACADapp.Documents(ACADapp.ActiveDocument.name)
        
        For Each entity In ss
            If entity.ObjectName = "AcDbText" Then
                Set text = entity
                currInsertionPoint = text.InsertionPoint
                If IsNumeric(text.TextString) And PtInPline(currInsertionPoint, pline) And floor < Val(text.TextString) Then
                    floor = Val(text.TextString)
                End If
            End If
        Next
        
        c = ss.Count - 1
        
        For Index = 1 To floor
        
            l = (max_x - min_x) / 2
            h = (max_y - min_y) / 2
        
            '创建文档
            Dim newdoc As AcadDocument
            Set newdoc = ACADapp.Documents.Add
            '保存
            ACADapp.ActiveDocument.SaveAs (path & name & "(" & num & ")" & "\分户图（第" & Index & "层）.dwg")
            
            For i = 0 To c
                ReDim ocollection(0 To 3) As AcadEntity
                Set entity = ss.Item(i)
                If entity.ObjectName = "AcDbText" Then
                    Set text = entity
                    Dim c_floor As Integer
                    c_floor = 1
                    currInsertionPoint = text.InsertionPoint
                    If (text.TextString = "混" Or text.TextString = "砼" Or text.TextString = "砖" Or text.TextString = "土" Or InStr(text.TextString, "半") Or InStr(text.TextString, "全") Or (text.TextString = "阁" And Index = floor) Or (text.TextString = "炮" And Index = floor)) And PtInPline(currInsertionPoint, pline) Then
                        Dim ce As AcadEntity
                        For Each ce In ss
                            Dim n_text As AcadText
                            If ce.ObjectName = "AcDbText" Then
                                Set n_text = ce
                                Dim cep As Variant
                                cep = n_text.InsertionPoint
                                If IsNumeric(n_text.TextString) And Sqr((cep(0) - currInsertionPoint(0)) ^ 2 + (cep(1) - currInsertionPoint(1)) ^ 2) < 1 Then
                                    c_floor = Val(n_text.TextString)
                                End If
                            End If
                        Next
                        If c_floor >= Index Then
                            Dim poly As AcadLWPolyline
                            For Each entity In ss
                                If entity.ObjectName = "AcDbPolyline" Then
                                    Set poly = entity
                                    Dim ax As Double
                                    Dim ay As Double
                                    Dim ix As Double
                                    Dim iy As Double
                                    ax = 0
                                    ay = 0
                                    ix = 99999999
                                    iy = 99999999
                                    Set ply = entity
                                    For j = 0 To UBound(ply.Coordinates) / 2
                                        x = ply.Coordinates(j * 2)
                                        y = ply.Coordinates(j * 2 + 1)
                                        If ax < x Then
                                            ax = x
                                        End If
                                        If ay < y Then
                                            ay = y
                                        End If
                                        If ix > x Then
                                            ix = x
                                        End If
                                        If iy > y Then
                                            iy = y
                                        End If
                                    Next
                                    If poly.Closed Then
                                        If PtInPline(currInsertionPoint, entity) Then
                                            Dim tp(0 To 2) As Double
                                            Dim lt As AcadText
                                            tp(0) = currInsertionPoint(0)
                                            tp(1) = currInsertionPoint(1)
                                            tp(2) = 0
                                            If InStr(text.TextString, "半") Or InStr(text.TextString, "全") Then
                                                Set lt = curdoc.ModelSpace.AddText("廊", tp, 0.5)
                                                Set ocollection(0) = lt
                                                lt.Delete
                                            Else
                                                Set ocollection(0) = text
                                            End If
                                            Dim bh As AcadText
                                            Dim at As AcadText
                                            tp(1) = currInsertionPoint(1) - 2
                                            If InStr(text.TextString, "半") = Index Then
                                                Set bh = curdoc.ModelSpace.AddText("②", tp, 0.5)
                                                tp(1) = currInsertionPoint(1) - 3
                                                Set at = curdoc.ModelSpace.AddText("" & Format(poly.Area / 2, ".00"), tp, 0.5)
                                            Else
                                                Set bh = curdoc.ModelSpace.AddText("①", tp, 1)
                                                tp(1) = currInsertionPoint(1) - 3
                                                Set at = curdoc.ModelSpace.AddText("" & Format(poly.Area, ".00"), tp, 0.5)
                                            End If
                                            Set ocollection(1) = entity
                                            Set ocollection(2) = bh
                                            Set ocollection(3) = at
                                            curdoc.CopyObjects ocollection, newdoc.ModelSpace
                                            bh.Delete
                                            at.Delete
                                            Exit For
                                        End If
                                    End If
                                End If
                            Next
                        End If
                    End If
                End If
            Next
            
            Dim frameObj As AcadLWPolyline
            Dim f_points(0 To 9) As Double
            Dim titleObj As AcadText
            Dim titleString As String
            Dim t_Point(0 To 2) As Double
            Dim t_height As Double
            Dim typeface As String
            Dim bold As Boolean
            Dim italic As Boolean
            Dim charset As Long
            Dim pitchandfamily As Long
            Dim dw As AcadText
            
             ' Define points of frame
            f_points(0) = c_x - l: f_points(1) = c_y + h
            f_points(2) = c_x + l: f_points(3) = c_y + h
            f_points(4) = c_x + l: f_points(5) = c_y - h
            f_points(6) = c_x - l: f_points(7) = c_y - h
            f_points(8) = c_x - l: f_points(9) = c_y + h
                
            ' Create frame
            Set frameObj = newdoc.ModelSpace.AddLightWeightPolyline(f_points)
            
            Dim pt() As Double
            Dim off As Double
            off = 0.1
            Dim strcom As String
            
            ThisDrawing.SendCommand "trim "
            
            ThisDrawing.SendCommand axEnt2lspEnt(frameObj) & vbCr
            Set offobj = offent(frameObj, off, pt(), True)
            For j = 0 To UBound(pt) Step 3
            strcom = strcom & pt(j)
            strcom = strcom & "," & pt(j + 1) & vbCr
            Next j
            strcom = strcom & pt(0)
            strcom = strcom & "," & pt(1) & vbCr
            strcom = strcom & Chr(9)
            ThisDrawing.SendCommand vbCr
            
            Dim sc() As String
            sc = Split(strcom, Chr(9))
            Dim Ct() As String
            
            For j = 1 To 3
            For i = 0 To UBound(sc) - 1
            DoEvents
            Dim pt1(2) As Double
            Dim pt2(2) As Double
            Ct = Split(sc(i), vbCr)
            For k = 0 To UBound(Ct) - 2
            le = k + 1
            tmp = Split(Ct(k), ",")
            pt1(0) = tmp(0): pt1(1) = tmp(1)
            tmp = Split(Ct(le), ",")
            pt2(0) = tmp(0): pt2(1) = tmp(1)
            
            ThisDrawing.Application.ZoomWindow pt1, pt2
            ThisDrawing.Application.ZoomCenter ThisDrawing.GetVariable("viewctr"), ThisDrawing.GetVariable("viewsize") * 1.5
                ThisDrawing.SendCommand "f " & Ct(k) & vbCr & Ct(le) & vbCr & vbCr
            Next k
            Next i
            Next j
            GoTo begindel
            
            
begindel:
            Set offobj = Nothing
            ReDim pt(0) As Double
            strcom = ""
            Set pp = Nothing
            ThisDrawing.SendCommand vbCr
            
            
            ThisDrawing.SendCommand "e "
            sendcom = "r cp "
            
            ThisDrawing.SendCommand "all "
            For i = 0 To UBound(sc) - 1
            ThisDrawing.SendCommand sendcom & sc(i) & vbCr
            Next i
            ThisDrawing.SendCommand vbCr
            
            frameObj.Delete
            
            If l <= h Then
                l = h * 210 / 297
            End If
            
            If l > h Then
                h = l * 297 / 210
            End If
            
            If l < 15 Then
                l = 15
                h = 15 * 297 / 210
            End If
            
            f_points(0) = c_x - l: f_points(1) = c_y + h
            f_points(2) = c_x + l: f_points(3) = c_y + h
            f_points(4) = c_x + l: f_points(5) = c_y - h
            f_points(6) = c_x - l: f_points(7) = c_y - h
            f_points(8) = c_x - l: f_points(9) = c_y + h
            
            Set frameObj = newdoc.ModelSpace.AddLightWeightPolyline(f_points)
            
            ' Define the title
            ACADapp.ActiveDocument.ActiveTextStyle.GetFont typeface, bold, italic, charset, pitchandfamily
            typeface = "宋体"
            ACADapp.ActiveDocument.ActiveTextStyle.SetFont typeface, bold, italic, charset, pitchandfamily
            titleString = "房产分户图"
            t_height = 0.8
            t_Point(0) = c_x: t_Point(1) = c_y + h + 4.5: t_Point(2) = 0
           
            Dim oldPDMODE As Integer
            Dim pointObj As AcadPoint
    
            ' Create title
            Set titleObj = ACADapp.ActiveDocument.ModelSpace.AddText(titleString, t_Point, t_height)
            
            oldPDMODE = ACADapp.ActiveDocument.GetVariable("PDMODE")
        
            Set pointObj = ACADapp.ActiveDocument.ModelSpace.AddPoint(t_Point)
            
            ACADapp.ActiveDocument.SetVariable "PDMODE", 2
                
            ACADapp.ActiveDocument.Application.ZoomAll
            
            titleObj.Alignment = acAlignmentRight
    
            titleObj.TextAlignmentPoint = t_Point
            ACADapp.ActiveDocument.Regen acActiveViewport
            
            titleObj.Alignment = acAlignmentCenter
            ACADapp.ActiveDocument.Regen acActiveViewport
            
            ACADapp.ActiveDocument.SetVariable "PDMODE", oldPDMODE
            
            Dim line As AcadLWPolyline
            Dim points(0 To 3) As Double
            
            points(0) = c_x - l: points(1) = c_y + h + 5.7
            points(2) = c_x + l: points(3) = c_y + h + 5.7
            
            Set line = ACADapp.ActiveDocument.ModelSpace.AddLightWeightPolyline(points)
            
            points(0) = c_x - l: points(1) = c_y + h + 5.7
            points(2) = c_x - l: points(3) = c_y + h
            
            Set line = ACADapp.ActiveDocument.ModelSpace.AddLightWeightPolyline(points)
            
            points(0) = c_x + l: points(1) = c_y + h + 5.7
            points(2) = c_x + l: points(3) = c_y + h
            
            Set line = ACADapp.ActiveDocument.ModelSpace.AddLightWeightPolyline(points)
            
            Dim str As String
            
            str = "单位：m.m2"
            t_height = 0.5
            t_Point(0) = c_x + l - 4: t_Point(1) = c_y + h + 5.9: t_Point(2) = 0
            Set dw = ACADapp.ActiveDocument.ModelSpace.AddText(str, t_Point, t_height)
            
            Dim spl As Double
            
            spl = 2 * l / 8
            
            Dim txt As AcadText
           
            str = "户主"
            t_height = 0.5
            t_Point(0) = c_x - l + 0.2: t_Point(1) = c_y + h + 3.5: t_Point(2) = 0
            Set txt = ACADapp.ActiveDocument.ModelSpace.AddText(str, t_Point, t_height)
            
            str = "" & name
            t_height = 0.5
            t_Point(0) = c_x - l + 2.5: t_Point(1) = c_y + h + 3.5: t_Point(2) = 0
            Set txt = ACADapp.ActiveDocument.ModelSpace.AddText(str, t_Point, t_height)
            
            str = "宗地代码"
            t_height = 0.5
            t_Point(0) = c_x - l + 2 * spl - 1.5: t_Point(1) = c_y + h + 3.5: t_Point(2) = 0
            Set txt = ACADapp.ActiveDocument.ModelSpace.AddText(str, t_Point, t_height)
            
            str = "11111111111"
            t_height = 0.5
            t_Point(0) = c_x - l + 3 * spl - 1.5: t_Point(1) = c_y + h + 3.5: t_Point(2) = 0
            Set txt = ACADapp.ActiveDocument.ModelSpace.AddText(str, t_Point, t_height)
            
            str = "专有建筑面积"
            t_height = 0.5
            t_Point(0) = c_x - l + 6 * spl - 1.5: t_Point(1) = c_y + h + 3.5: t_Point(2) = 0
            Set txt = ACADapp.ActiveDocument.ModelSpace.AddText(str, t_Point, t_height)
            
            str = "133.08"
            t_height = 0.5
            t_Point(0) = c_x - l + 0# + 7 * spl: t_Point(1) = c_y + h + 3.5: t_Point(2) = 0
            Set txt = ACADapp.ActiveDocument.ModelSpace.AddText(str, t_Point, t_height)
            
            points(0) = c_x - l: points(1) = c_y + h + 4.3
            points(2) = c_x + l: points(3) = c_y + h + 4.3
            
            Set line = ACADapp.ActiveDocument.ModelSpace.AddLightWeightPolyline(points)
            
            points(0) = c_x - l: points(1) = c_y + h + 3.3
            points(2) = c_x + l: points(3) = c_y + h + 3.3
            
            Set line = ACADapp.ActiveDocument.ModelSpace.AddLightWeightPolyline(points)
            
            points(0) = c_x - l + 2: points(1) = c_y + h + 4.3
            points(2) = c_x - l + 2: points(3) = c_y + h
            
            Set line = ACADapp.ActiveDocument.ModelSpace.AddLightWeightPolyline(points)
            
            str = "幢号"
            t_height = 0.5
            t_Point(0) = c_x - l + 0.2: t_Point(1) = c_y + h + 2.5: t_Point(2) = 0
            Set txt = ACADapp.ActiveDocument.ModelSpace.AddText(str, t_Point, t_height)
            
            str = "F0001"
            t_height = 0.5
            t_Point(0) = c_x - l + 2.5: t_Point(1) = c_y + h + 2.5: t_Point(2) = 0
            Set txt = ACADapp.ActiveDocument.ModelSpace.AddText(str, t_Point, t_height)
            
            str = "房屋用途"
            t_height = 0.5
            t_Point(0) = c_x - l + 2 * spl - 1.5: t_Point(1) = c_y + h + 2.5: t_Point(2) = 0
            Set txt = ACADapp.ActiveDocument.ModelSpace.AddText(str, t_Point, t_height)
            
            str = "住宅"
            t_height = 0.5
            t_Point(0) = c_x - l + 3 * spl - 1.5: t_Point(1) = c_y + h + 2.5: t_Point(2) = 0
            Set txt = ACADapp.ActiveDocument.ModelSpace.AddText(str, t_Point, t_height)
            
            str = "总层数"
            t_height = 0.5
            t_Point(0) = c_x - l + 4 * spl - 1.5: t_Point(1) = c_y + h + 2.5: t_Point(2) = 0
            Set txt = ACADapp.ActiveDocument.ModelSpace.AddText(str, t_Point, t_height)
            
            str = "" & floor
            t_height = 0.5
            t_Point(0) = c_x - l + 5 * spl - 1.5: t_Point(1) = c_y + h + 2.5: t_Point(2) = 0
            Set txt = ACADapp.ActiveDocument.ModelSpace.AddText(str, t_Point, t_height)
            
            str = "分摊建筑面积"
            t_height = 0.5
            t_Point(0) = c_x - l + 6 * spl - 1.5: t_Point(1) = c_y + h + 2.5: t_Point(2) = 0
            Set txt = ACADapp.ActiveDocument.ModelSpace.AddText(str, t_Point, t_height)
            
            str = "/"
            t_height = 0.5
            t_Point(0) = c_x - l + 0.2 + 7 * spl: t_Point(1) = c_y + h + 2.5: t_Point(2) = 0
            Set txt = ACADapp.ActiveDocument.ModelSpace.AddText(str, t_Point, t_height)
            
            points(0) = c_x - l: points(1) = c_y + h + 3.3
            points(2) = c_x + l: points(3) = c_y + h + 3.3
            
            Set line = ACADapp.ActiveDocument.ModelSpace.AddLightWeightPolyline(points)
            
            points(0) = c_x - l: points(1) = c_y + h + 2.3
            points(2) = c_x + l: points(3) = c_y + h + 2.3
            
            Set line = ACADapp.ActiveDocument.ModelSpace.AddLightWeightPolyline(points)
            
            points(0) = c_x - l: points(1) = c_y + h + 1.3
            points(2) = c_x + l: points(3) = c_y + h + 1.3
            
            Set line = ACADapp.ActiveDocument.ModelSpace.AddLightWeightPolyline(points)
            
            str = "户号"
            t_height = 0.5
            t_Point(0) = c_x - l + 0.2: t_Point(1) = c_y + h + 1.5: t_Point(2) = 0
            Set txt = ACADapp.ActiveDocument.ModelSpace.AddText(str, t_Point, t_height)
            
            str = "0001"
            t_height = 0.5
            t_Point(0) = c_x - l + 2.5: t_Point(1) = c_y + h + 1.5: t_Point(2) = 0
            Set txt = ACADapp.ActiveDocument.ModelSpace.AddText(str, t_Point, t_height)
            
            points(0) = c_x - l + 5.5: points(1) = c_y + h + 4.3
            points(2) = c_x - l + 5.5: points(3) = c_y + h + 1.3
            
            Set line = ACADapp.ActiveDocument.ModelSpace.AddLightWeightPolyline(points)
            
            str = "建成年代"
            t_height = 0.5
            t_Point(0) = c_x - l + 2 * spl - 1.5: t_Point(1) = c_y + h + 1.5: t_Point(2) = 0
            Set txt = ACADapp.ActiveDocument.ModelSpace.AddText(str, t_Point, t_height)
            
            points(0) = c_x - l + 2 * spl + 2: points(1) = c_y + h + 4.3
            points(2) = c_x - l + 2 * spl + 2: points(3) = c_y + h + 1.3
            
            Set line = ACADapp.ActiveDocument.ModelSpace.AddLightWeightPolyline(points)
            
            str = "1990年10月"
            t_height = 0.5
            t_Point(0) = c_x - l + 3 * spl - 1.5: t_Point(1) = c_y + h + 1.5: t_Point(2) = 0
            Set txt = ACADapp.ActiveDocument.ModelSpace.AddText(str, t_Point, t_height)
            
            points(0) = c_x - l + 3 * spl + 2.2: points(1) = c_y + h + 3.3
            points(2) = c_x - l + 3 * spl + 2.2: points(3) = c_y + h + 1.3
            
            Set line = ACADapp.ActiveDocument.ModelSpace.AddLightWeightPolyline(points)
            
            str = "所在层次"
            t_height = 0.5
            t_Point(0) = c_x - l + 4 * spl - 1.5: t_Point(1) = c_y + h + 1.5: t_Point(2) = 0
            Set txt = ACADapp.ActiveDocument.ModelSpace.AddText(str, t_Point, t_height)
            
            points(0) = c_x - l + 4 * spl + 2: points(1) = c_y + h + 3.3
            points(2) = c_x - l + 4 * spl + 2: points(3) = c_y + h + 1.3
            
            Set line = ACADapp.ActiveDocument.ModelSpace.AddLightWeightPolyline(points)
            
            str = "0" & Index
            t_height = 0.5
            t_Point(0) = c_x - l + 5 * spl - 1.5: t_Point(1) = c_y + h + 1.5: t_Point(2) = 0
            Set txt = ACADapp.ActiveDocument.ModelSpace.AddText(str, t_Point, t_height)
            
            points(0) = c_x - l + 5 * spl + 2: points(1) = c_y + h + 4.3
            points(2) = c_x - l + 5 * spl + 2: points(3) = c_y + h + 1.3
            
            Set line = ACADapp.ActiveDocument.ModelSpace.AddLightWeightPolyline(points)
            
            str = "建筑面积"
            t_height = 0.5
            t_Point(0) = c_x - l + 6 * spl - 1.5: t_Point(1) = c_y + h + 1.5: t_Point(2) = 0
            Set txt = ACADapp.ActiveDocument.ModelSpace.AddText(str, t_Point, t_height)
            
            points(0) = c_x - l + 6 * spl + 3: points(1) = c_y + h + 4.3
            points(2) = c_x - l + 6 * spl + 3: points(3) = c_y + h + 1.3
            
            Set line = ACADapp.ActiveDocument.ModelSpace.AddLightWeightPolyline(points)
            
            str = "139.06"
            t_height = 0.5
            t_Point(0) = c_x - l + 0.2 + 7 * spl: t_Point(1) = c_y + h + 1.5: t_Point(2) = 0
            Set txt = ACADapp.ActiveDocument.ModelSpace.AddText(str, t_Point, t_height)
            
            str = "坐落"
            t_height = 0.5
            t_Point(0) = c_x - l + 0.2: t_Point(1) = c_y + h + 0.5: t_Point(2) = 0
            Set txt = ACADapp.ActiveDocument.ModelSpace.AddText(str, t_Point, t_height)
            
            str = "攀枝花市米易县"
            t_height = 0.5
            t_Point(0) = c_x - l + 0.2 + spl: t_Point(1) = c_y + h + 0.5: t_Point(2) = 0
            Set txt = ACADapp.ActiveDocument.ModelSpace.AddText(str, t_Point, t_height)
            
            
            str = "北"
            t_height = 0.5
            t_Point(0) = c_x + l - 2: t_Point(1) = c_y + h - 1: t_Point(2) = 0
            Set txt = ACADapp.ActiveDocument.ModelSpace.AddText(str, t_Point, t_height)
                  
            str = "绘制日期：2019年12月13日"
            t_height = 0.5
            t_Point(0) = c_x + l - 10: t_Point(1) = c_y - h + 1: t_Point(2) = 0
            Set txt = ACADapp.ActiveDocument.ModelSpace.AddText(str, t_Point, t_height)
            
            str = "表示半面积"
            t_height = 0.5
            t_Point(0) = c_x + l - 4: t_Point(1) = c_y - h + 3: t_Point(2) = 0
            Set txt = ACADapp.ActiveDocument.ModelSpace.AddText(str, t_Point, t_height)
            
            str = "表示全面积"
            t_height = 0.5
            t_Point(0) = c_x + l - 4: t_Point(1) = c_y - h + 4: t_Point(2) = 0
            Set txt = ACADapp.ActiveDocument.ModelSpace.AddText(str, t_Point, t_height)
            
            str = "备注"
            t_height = 0.5
            t_Point(0) = c_x + l - 4: t_Point(1) = c_y - h + 5: t_Point(2) = 0
            Set txt = ACADapp.ActiveDocument.ModelSpace.AddText(str, t_Point, t_height)
            
            str = "1:" & Int(2 * l * 1000 / 200)
            t_height = 0.5
            t_Point(0) = c_x: t_Point(1) = c_y - h - 1: t_Point(2) = 0
            
            Set txt = ACADapp.ActiveDocument.ModelSpace.AddText(str, t_Point, t_height)
            
            str = "米易县不动产登记中心"
            t_height = 0.5
            t_Point(0) = c_x - l - 1: t_Point(1) = c_y - h + 10: t_Point(2) = 0
            
            Set txt = ACADapp.ActiveDocument.ModelSpace.AddText(str, t_Point, t_height)
            txt.Rotate t_Point, 4.7123889803847
            txt.Update
            
            'define arrow
            Dim solidObj As AcadSolid
            Dim point1(0 To 2) As Double
            Dim point2(0 To 2) As Double
            Dim point3(0 To 2) As Double
            Dim point4(0 To 2) As Double
            
            point1(0) = c_x + l - 2.25: point1(1) = c_y + h - 4: point1(2) = 0
            point2(0) = c_x + l - 1.75: point2(1) = c_y + h - 1.8: point2(2) = 0
            point3(0) = c_x + l - 1.75: point3(1) = c_y + h - 3: point3(2) = 0
            point4(0) = c_x + l - 2.25: point4(1) = c_y + h - 4: point4(2) = 0
        
            ' Create the solid object in model space
            Set solidObj = ThisDrawing.ModelSpace.AddSolid(point1, point2, point3, point4)
            
            point1(0) = c_x + l - 1.25: point1(1) = c_y + h - 4: point1(2) = 0
            point2(0) = c_x + l - 1.75: point2(1) = c_y + h - 1.8: point2(2) = 0
            point3(0) = c_x + l - 1.75: point3(1) = c_y + h - 3: point3(2) = 0
            point4(0) = c_x + l - 1.25: point4(1) = c_y + h - 4: point4(2) = 0
        
            ' Create the solid object in model space
            Set solidObj = ThisDrawing.ModelSpace.AddSolid(point1, point2, point3, point4)
            
             '保存
            ACADapp.ActiveDocument.Save
            
            ACADapp.ActiveDocument.Close
           
        Next
        
        ss.Delete
        
    End If
    
Next

End Sub
