Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True

Public Sub dad()

    Dim path As String
    Dim source As String
    
    path = "C:\chengguo\" '保存路径

    If Dir(path, vbDirectory) = "" Then
        MkDir (path)
    End If
    
    UserForm1.Show
    If UserForm1.TextBox1.text = "" Then
        source = "C:\Users\PWB\Desktop\cad\米易房地一体模板-0422\00.档案袋.docx"
    Else
        source = UserForm1.TextBox1.text & "00.档案袋.docx"
    End If

    Dim entity As AcadEntity
    Dim polyline As AcadLWPolyline
    
    ThisDrawing.Utility.GetEntity entity, basePnt, "选取JZD多段线"
    
    While Not (entity.ObjectName = "AcDbPolyline" And entity.Layer = "JZD")
        MsgBox "不是多段线或不在JZD图层，重新选择"
        ThisDrawing.Utility.GetEntity entity, basePnt, "选取JZD多段线"
    Wend
    
    Set polyline = entity
    max_x = 0
    max_y = 0
    min_x = 99999999
    min_y = 99999999
    For Index = 0 To UBound(polyline.Coordinates) / 2
        x = polyline.Coordinates(Index * 2)
        y = polyline.Coordinates(Index * 2 + 1)
        If max_x < x Then
            max_x = x
        End If
        If max_y < y Then
            max_y = y
        End If
        If min_x > x Then
            min_x = x
        End If
        If min_y > y Then
            min_y = y
        End If
    Next
    
    Dim ss As AcadSelectionSet
    
    If ThisDrawing.SelectionSets.Count <> 0 Then
        For Each ss In ThisDrawing.SelectionSets
            ss.Delete
            Exit For
        Next
    End If
    Set ss = ThisDrawing.SelectionSets.Add("s")
    
    Dim point1a(0 To 2) As Double
    Dim point2a(0 To 2) As Double
    
    c_x = (min_x + max_x) / 2
    c_y = (min_y + max_y) / 2
    l = (max_x - min_x) / 2
    h = (max_y - min_y) / 2
    
    point1a(0) = c_x - l
    point1a(1) = c_y - h
    point2a(0) = c_x + l
    point2a(1) = c_y + h
    
    Dim gpCode(0) As Integer
    Dim dataValue(0) As Variant
    gpCode(0) = 8
    dataValue(0) = "JZD"
    
    Dim groupCode As Variant, dataCode As Variant
    groupCode = gpCode
    dataCode = dataValue
    
    ss.Select acSelectionSetWindow, point1a, point2a, groupCode, dataCode
    
    Dim text As AcadText
    Dim name As String
    Dim flag As Boolean
    Dim num As String
    Dim zdbh As String
    Dim dl As String
    Dim sfzh As String
    Dim hkbh As String
    Dim year As String
    Dim month As String
    Dim day As String
    Dim sx As String
    Dim hour As String
    
    For Each entity In ss
        If entity.ObjectName = "AcDbText" Then
            Set text = entity
            name = text.TextString
            '中文字符且长度大于1
            If Len(name) > 2 And InStr(name, "JC") Then
                num = name
            End If
            If Len(name) > 1 And ((AscW(Mid(name, 1, 1)) > -40870 And AscW(Mid(name, 1, 1)) < -19967) Or (AscW(Mid(name, 1, 1)) < 40870 And AscW(Mid(name, 1, 1)) > 19967)) Then
                flag = True
                Exit For
            End If
        End If
    Next
    
    If flag Then
    
        If Dir(path & name & "(" & num & ")", vbDirectory) = "" Then
            MkDir (path & name & "(" & num & ")")
        End If
        
        FileCopy source, path & name & "(" & num & ")\00.档案袋.docx"
        
        Dim xdataOut As Variant
        Dim xtypeOut As Variant
        text.GetXData "", xtypeOut, xdataOut
        
        Dim oword As Word.Application
        On Error Resume Next
        Set oword = GetObject(, "Word.Application")
        If Err.Number <> 0 Then
            Set oword = CreateObject("Word.Application")
        End If
        
        Dim doc As Word.Document
        Set doc = oword.Documents.Open(path & name & "(" & num & ")\00.档案袋.docx")
    
        With Selection.Find
            .ClearFormatting
            .text = "冉光祥"
            .Replacement.ClearFormatting
            .Replacement.text = name
            .Execute Replace:=wdReplaceAll, Forward:=True, _
            Wrap:=wdFindContinue

        End With
        
        doc.Save
        doc.Close
        
    Else
        MsgBox "未找到标注"
    End If
    
    
End Sub

Function ReplaceText(findval As String, replaceValue As String)
   
End Function

Attribute VB_Name = "UserForm1"
Attribute VB_Base = "0{7DDDACAF-F6AD-40DD-BBC2-2DF79546A88A}{FA0E4331-49E3-4542-AD74-36955935B33E}"
Attribute VB_GlobalNameSpace = False
Attribute VB_Creatable = False
Attribute VB_PredeclaredId = True
Attribute VB_Exposed = False
Attribute VB_TemplateDerived = False
Attribute VB_Customizable = False
Private Sub ListBox1_Click()

End Sub

Private Sub CommandButton1_Click()
    UserForm1.Hide
End Sub
